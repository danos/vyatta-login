module vyatta-system-login-v1 {
	namespace "urn:vyatta.com:mgmt:vyatta-system-login:1";
	prefix vyatta-system-login-v1;

	import vyatta-types-v1 {
		prefix types;
	}
	import ietf-yang-types {
		prefix ytypes;
	}
	import vyatta-system-v1 {
		prefix system;
	}
	import configd-v1 {
		prefix configd;
	}

	organization "AT&T Inc.";
	contact
		"AT&T
		 Postal: 208 S. Akard Street
		         Dallas, TX 75202
		 Web: www.att.com";

	description
		"Copyright (c) 2017-2021, AT&T Intellectual Property.
		 All rights reserved.

		 Copyright (c) 2014-2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 System login configuration";

	revision 2021-09-12 {
		description "RPC for password renewal.";
	}
	revision 2021-05-12 {
		description "Obsolete RADIUS configuration.";
	}
	revision 2021-01-18 {
		description "Add new state node for date and time when
                 user's password expires.
                 Deprecate RADIUS configuration.";
	}
	revision 2018-12-18 {
		description "Remove invalid metachars from pattern string.
			     Add RADIUS system-user login feature.
			     Remove variable expansion from error message.";
	}
	revision 2018-08-28 {
		description "New yang user state model: user-info";
	}
	revision 2018-06-14 {
		description "Adds minimum password requirement in plaintext_pass syntax validate";
	}
	revision 2018-04-09 {
		 description "Verify system login session-timeout set before max-sessions.";
	}
	revision 2017-11-27 {
		 description "Add support to limit maximum number of concurrent login sessions";
	}
	revision 2016-06-28 {
		description "Create grouping for radius-server.";
	}
	revision 2015-12-04 {
		description "Convert comp_help extension to description.";
	}
	revision 2015-08-14 {
		description "Initial revision of version 1.";
	}
	feature radius-system-user-login {
		description "RADIUS system-user login feature";
	}
	grouping radius-server-group {
		list radius-server {
			status obsolete;
			if-feature radius-system-user-login;
			description "Radius server authentication";
			configd:help "Radius server authentication";
			key "tagnode";
			leaf tagnode {
				type types:ipv4-address;
				description "Radius server authentication";
				configd:help "Radius server authentication";
			}
			leaf port {
				type uint32 {
					range 1..65535;
				}
				description "Radius port";
				configd:help "Radius port";
				default "1812";
			}
			leaf secret {
				type string;
				description "Secret for radius access";
				configd:help "Secret for radius access";
				mandatory true;
			}
			leaf timeout {
				type uint32 {
					range 1..30;
				}
				description "Timeout in seconds for radius session";
				configd:help "Timeout for radius session";
				default "2";
			}
		}

	}

	augment /system:system {
		container login {
			configd:priority "400";
			configd:help "User login";
			configd:delete "/opt/vyatta/share/tmplscripts/system/login/configd_delete.sh";
			configd:end "/opt/vyatta/sbin/vyatta_update_login.pl --system";
			leaf session-timeout {
				type uint32 {
					range 0..1000000;
				}
				configd:help "Idle Session timeout";
				default "0";
				configd:update "/opt/vyatta/share/tmplscripts/system/login/session-timeout/configd_update.sh";
			}
			uses radius-server-group;
			list group {
				configd:help "Group name";
				configd:update "/opt/vyatta/share/tmplscripts/system/login/group/configd_update.sh";
				configd:delete "/opt/vyatta/share/tmplscripts/system/login/group/configd_delete.sh";
				key "tagnode";
				leaf tagnode {
					type string;
					configd:help "Group name";
				}
				leaf description {
					type string;
					configd:help "Description";
				}
			}
			leaf max-sessions {
			     configd:help "Maximum number of concurrent login sessions";
			     description  "Maximum number of concurrent login sessions";
			     type uint32 {
			     	  range 1..max;
			     }
			     must "../session-timeout > 0" {
                                error-message "system login session-timeout must be > 0";
			     }

			     configd:update "/opt/vyatta/share/tmplscripts/system/login/max-sessions/configd_update.sh";
			     configd:delete "/opt/vyatta/share/tmplscripts/system/login/max-sessions/configd_delete.sh";
			}
			list user {
				configd:help "User account information";
				key "tagnode";
				leaf tagnode {
					type string {
						pattern '[a-zA-Z_][a-zA-Z0-9_-]*' {
							configd:error-message "Username should only contain lower case letters, digits, underscores or dashes"; 
						}
						configd:syntax "/opt/vyatta/share/tmplscripts/system/login/user/configd_syntax1.cli";
					}
					configd:help "User account information";
				}
				container authentication {
					configd:help "Authentication password";
					leaf plaintext-password {
						type string {
							configd:syntax "/opt/vyatta/share/tmplscripts/system/login/user/authentication/plaintext-password/configd_syntax.cli";
                            length 1..max;
						}
						description "Plaintext password for encryption. Passwords must adhere to the password requirements";
						configd:secret "true";
						configd:help "Plaintext password for encryption. Passwords must adhere to the password requirements";
						configd:subst "/opt/vyatta/share/tmplscripts/system/login/user/authentication/plaintext-password/configd_subst1.cli";
					}
					list public-keys {
						configd:help "Remote access public keys";
						configd:validate "/opt/vyatta/share/tmplscripts/system/login/user/authentication/public-keys/configd_validate1.cli";
						configd:validate "/opt/vyatta/share/tmplscripts/system/login/user/authentication/public-keys/configd_validate2.cli";
						key "tagnode";
						leaf tagnode {
							type string;
							configd:help "Remote access public keys";
						}
						leaf options {
							type string;
							configd:help "Additional public key options";
						}
						leaf key {
							type string {
								pattern '[0-9A-Za-z\+/=]*' {
									error-message "Invalid public key character not base-64";
								}
							}
							description "The public key is usually several hundred bytes long (because of the
								     size of the public key encoding). Use the loadkey tool to read the key
								     from a URL or file.";
							configd:help "Public key value (base64-encoded)";
						}
						leaf type {
							type string {
								configd:syntax "/opt/vyatta/share/tmplscripts/system/login/user/authentication/public-keys/type/configd_syntax1.cli";
							}
							configd:help "Public key type";
							configd:allowed "/opt/vyatta/share/tmplscripts/system/login/user/authentication/public-keys/type/configd_allowed.sh";
						}
					}
					leaf encrypted-password {
						type string {
							configd:syntax "/opt/vyatta/share/tmplscripts/system/login/user/authentication/encrypted-password/configd_syntax1.cli";
						}
						configd:secret "true";
						configd:help "Encrypted password";
					}
				}
				leaf home-directory {
					type string;
					configd:help "Home directory";
				}
				leaf-list group {
					type string {
						pattern '[a-zA-Z_][a-zA-Z0-9_-]*';
						configd:syntax "/opt/vyatta/share/tmplscripts/system/login/user/group/configd_syntax1.cli";
					}
					ordered-by "user";
					configd:help "Additional group membership";
					configd:allowed "/opt/vyatta/share/tmplscripts/system/login/user/group/configd_allowed.sh";
					configd:validate "/opt/vyatta/share/tmplscripts/system/login/user/group/configd_validate1.cli";
				}
				leaf level {
					type enumeration {
						enum "admin" {
							configd:help "Administrators";
						}
						enum "operator" {
							configd:help "Operators";
						}
						enum "superuser" {
							configd:help "Superusers";
						}
					}
					configd:help "User privilege level";
					default "admin";
					configd:allowed "/opt/vyatta/share/tmplscripts/system/login/user/level/configd_allowed.sh";
				}
				leaf full-name {
					type string {
						pattern '[^:]*' {
							error-message "Cannot use ':' in full name";
						}
					}
					configd:help "Full name of the user (use quotes for names with spaces)";
				}
			}
			container banner {
				configd:help "System login banners";
				leaf pre-login {
					type string;
					description "Pre-login banner

						     Example: '\\n\\n\\tUNAUTHORIZED USE OF THIS SYSTEM\\nIS PROHIBITED!\\n'";
					configd:help "System login banner pre-login";
					configd:update "/opt/vyatta/share/tmplscripts/system/login/banner/pre-login/configd_update.sh";
					configd:delete "/opt/vyatta/share/tmplscripts/system/login/banner/pre-login/configd_delete.sh";
				}
				leaf post-login {
					type string;
					description "Post-login banner

						     Example: '\\n\\n\\tWelcome to Vyatta!\\n'";
					configd:help "System login banner post-login";
					configd:update "/opt/vyatta/share/tmplscripts/system/login/banner/post-login/configd_update.sh";
					configd:delete "/opt/vyatta/share/tmplscripts/system/login/banner/post-login/configd_delete.sh";
				}
			}
			container user-info {
				config false;
				description "State of users configured on the system";
				configd:get-state "/opt/vyatta/sbin/system-login-information --action=get-state";
				list user {
					key "name";
					leaf name {
						description "Username";
						type string;
					}
					leaf type {
						description "Account type";
						type enumeration {
							enum "vyatta" {
								description "Vyatta generated user account";
							}
							enum "other" {
								description "Other linux system account";
							}
							enum "locked" {
								description "Locked linux system account";
							}
						}
					}
					leaf last-login {
						description "The data and time when the user last logged in";
						type union {
							type ytypes:date-and-time;
							type string {
								pattern "never logged in";
							}
						}	
					}
					leaf password-expiry {
						description "The date and time when the user's password expires";
						type union {
							type ytypes:date-and-time;
							type string {
								pattern "never";
							}
						}
					}
				}
			}
		}
	}

	rpc verify-password {
		description "Verify current password for user";
		input {
			leaf current-password {
				description "Current password in plaintext";
				mandatory true;
				type string {
					length 1..max;
				}
			}
		}
		configd:call-rpc "vyatta-password-rpc verify-password";
	}
	rpc change-password {
		description "Change password for user";
		input {
			leaf current-password {
				description "Current password in plaintext";
				mandatory true;
				type string {
					length 1..max;
				}
			}
			leaf new-password {
				description "New password in plaintext";
				mandatory true;
				type string {
					length 1..max;
				}
			}
		}
		configd:call-rpc "vyatta-password-rpc change-password";
	}
}
