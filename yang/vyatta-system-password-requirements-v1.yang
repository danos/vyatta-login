module vyatta-system-password-requirements-v1 {
	namespace "urn:vyatta.com:mgmt:vyatta-system-password-requirements:1";
	prefix vyatta-system-password-requirements-v1;

	import vyatta-system-v1 {
		prefix system;
	}
	import configd-v1 {
		prefix configd;
	}

	organization "AT&T Inc.";
	contact
		"AT&T
		 Postal: 208 S. Akard Street
				 Dallas, TX 75202
		 Web: www.att.com";

	description
		"Copyright (c) 2018-2020, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 System password requirement configuration";

	revision 2020-12-15 {
		description "Add support for password expiration and history features.";
	}
	revision 2018-11-29 {
		description "Correctly name user-match as disable-gecos-check. Deprecates
			password requirements user-match node";
	}
	revision 2018-08-28 {
		description "Initial revision of version 1.";
	}

	augment /system:system {
		container password {
			description "System password settings.";
			configd:help "System password settings.";
			container requirements {
				description "This contains the password requirements settings for the system.";
				configd:help "Minimum password requirements.";
				configd:end "/opt/vyatta/sbin/update_password_quality.pl";
				configd:update "/opt/vyatta/sbin/update_password_quality.pl";
				presence "Enable system password requirements.";
				container classes {
					description "Password character classes.";
					configd:help "Password character classes.";
					leaf upper {
						description "Password must contain at least N uppercase characters.";
						configd:help "Must contain at least N uppercase characters";
						type uint8;
						default 0;
					}
					leaf lower {
						description "Password must contain at least N lowercase characters.";
						configd:help "Must contain at least N lowercase characters";
						type uint8;
						default 0;
					}
					leaf digits {
						description "Password must contain at least N digits";
						configd:help "Must contain at least N digits";
						type uint8;
						default 0;
					}
					leaf others {
						description "Password must contain at least X punctuation characters.";
						configd:help "Must contain at least X punctuation characters";
						type uint8;
						default 0;
					}
					leaf min-class {
						description "The minimum number of required classes of characters (digits, uppercase, lowercase, punct)";
						configd:help "Minimum matched characters classes. ( 0 = disables )";
						type uint8 {
							range 0..4;
						}
						default 3;
					}
				}
				leaf length {
					description "Minimum length of the password.";
					configd:help "Minimum length of the password";
					type uint8 {
						range 6..255;
					}
					default 6;
				}
				leaf user-match {
					description "Passwords cannot match username.";
					configd:help "Passwords cannot match username";
					status deprecated;
					type boolean;
					default true;
				}
				leaf disable-gecos-check {
					description "Disables Pwquality gecos check which matches
						password against known user traits such as name,
						address, and phone number";
					configd:help "Disables Pwquality gecos check";
					type empty;
				}
				container history {
					description "Password history configuration.";
					configd:help "Password history configuration";
					leaf forbid-previous {
						description "Number of previous passwords that are forbidden for reuse.";
						configd:help "Number of previous passwords that are forbidden for reuse";
						type uint16 {
							range 1..10;
						}
					}
				}
				container expiration {
					description "Password expiration configuration.";
					configd:help "Password expiration configuration";
					leaf maximum-days {
						description "Maximum days a password may be used.";
						configd:help "Maximum days a password may be used";
						type int32 {
							range 1..99999;
						}
					}
				}
			}
		}
	}
}
