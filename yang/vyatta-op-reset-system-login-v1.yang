module vyatta-op-reset-system-login-v1 {
	namespace "urn:vyatta.com:mgmt:vyatta-op-reset-system-login:1";
	prefix vyatta-op-reset-system-login-v1;

	import vyatta-opd-extensions-v1 {
		prefix opd;
	}
	import vyatta-op-reset-v1 {
		prefix reset;
	}
	import vyatta-op-reset-system-v1 {
		prefix system;
	}

	organization "AT&T Inc.";
	contact
		"AT&T
		 Postal: 208 S. Akard Street
				 Dallas, TX 75202
		 Web: www.att.com";

	description
		"Copyright (c) 2018-2019, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		Defines the operational commands relevant to 'system login'.";

	revision 2018-08-06 {
		description "Initial version";
	}

	opd:augment /reset:reset/system:system {
		opd:command login {
			opd:help "Reset system login information.";

			opd:command users {
				opd:help "Reset user account information.";

				opd:command account-disabled {
					opd:help "Reset system users account lockout timers";
					
					opd:argument user {
						opd:help "Reset users lockout timer.";
						opd:on-enter "/opt/vyatta/bin/vyatta_tally_op --action=reset $6";
						opd:allowed "/opt/vyatta/bin/vyatta_tally_op --action=show-prompt";
                        type string;
				    }
			    }
            }
		}
	}
}
